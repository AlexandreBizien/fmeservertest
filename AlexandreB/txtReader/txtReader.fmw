FME workspace txtReader.fmw

Parameters:
- SourceDataset_TEXTLINE = C:\Users\a_bizien\Desktop\license_G0183BDD3.txt   # Source Text File(s)

Readers:
- TEXTLINE_1: TEXTLINE from $(SourceDataset_TEXTLINE)

text_line (reader TEXTLINE_1)
    attributes: text_line_data buffer
    -> Logger
Logger
    LOG_FEATURE = LOG_ONLY
    MAXCOORDS = 20
    MAXFEATS = 20
    MESSAGE = Feature is:
    SEVERITY = INFO
