FME workspace exportv3.fmw
Title: Export GTF
Description: Export de traitements GEX depuis GTF
History: 20120601,M. Ambrosy,v3 : Les traitements sont dans le dossier workspace,20140306,M. Ambrosy,Refonte et gestion des métadonnées,20140307,M. Ambrosy,Désactivation des groupes,20150109,M. Ambrosy,Mises à jour majeures

Parameters:
- idWorkspaceList = 35   # id séparés par un espace 
- destGexFile = C:\antoine_non_sauv\2017_11_gtf_export\test.gex   # Fichier Gtf Export (.gex) 
- GTF_CONNECTION_STRING =   # Chaîne de connexion à la base GTF 
- dbDatabase:   # Python Script
      import fmeobjects
      import string
      connection_string = string.split(FME_MacroValues['GTF_CONNECTION_STRING'],',')
      return connection_string[2]

Readers:
- POSTGRES_1: POSTGRES from $(dbDatabase)

Writers:
- GML_1: GML to test.gml

Note: s_gtf.workspace
workspace (reader POSTGRES_1)
    attributes: workspace_id int4,PRIKEY, name varchar(100),BTREE, description text, subscription bool, fmw_file varchar(150), category_id int4,BTREE, success_action_id int4, failed_action_id int4, survey bool, form_type varchar(10), legal_terms_conditions text, usage text, requirements text, history text, last_save_date timestamp, last_save_build varchar(255), file_encoding varchar(50), title varchar(255), key varchar(40), email_template_id int4, owner int4, creation_date date, locked bool, tag varchar(100)
    -> ParameterFetcher
Note: On est obligé de récupèrer / le paramètre sous forme d'attribut / pour le modifier ensuite
ParameterFetcher
    ATTR_LIST = _idWorkspaceList {$(idWorkspaceList)}
    -> StringReplacer
StringReplacer
    CASE = no
    FIND_TEXT = " "
    NO_MATCH = _FME_NO_OP_
    REGEXP = no
    REPLACE_TEXT = ,
    SRC_ATTRS = _idWorkspaceList
    -> Tester
Tester
    BOOL_OP = OR
    TEST_CLAUSE = TEST @Value(workspace_id) IN @Value(_idWorkspaceList)
    PASSED -> AttributeRemover
AttributeRemover
    REMOVE_ATTRS = _idWorkspaceList
    -> AttributeRenamer
AttributeRenamer
    ATTR_LIST = name,label_name,""
    -> FeatureMerger_3 [REQUESTOR]
Creator
    GEOMTYPE = Geometry Object
    NUM = 1
    CREATED -> TempPathnameCreator_2
TempPathnameCreator_2
    PATHNAME_ATTR = _tempDir
    -> FeatureMerger_2 [SUPPLIER]
FeatureMerger_2
    ATTR_ACCUM_MODE = Merge Supplier
    ATTR_CONFLICT_RES = Use Requestor
    CLEANING_TOLERANCE = None
    IGNORE_NULLS = No
    JOIN_KEYS = 1 1 AUTO
    MERGE_TYPE = Attributes Only
    PROCESS_DUPS = No
    REJECT_NULL_MISSING_KEYS = No
    SUPPLIERS_FIRST = No
    MERGED -> PythonCaller
    MERGED -> FeatureMerger [SUPPLIER]
Note: Copie des fichiers vers temp
PythonCaller
    PYTHONSOURCE:
      import fmeobjects
      import os
      import shutil

      def FeatureProcessor(feature):
          fme_mf_dir = os.path.normpath(FME_MacroValues['FME_MF_DIR'])
          workspace_id = feature.getAttribute('workspace_id')
          projectsourcedir = fme_mf_dir + '//..//..//' + workspace_id
          if os.path.exists(projectsourcedir):
              try:
                  shutil.copytree(projectsourcedir, feature.getAttribute('_tempDir') + '//' + workspace_id, symlinks=False, ignore=None)
              except:
                  print "Une erreur PYTHON est survenue !"
                  raise
    PYTHONSYMBOL = FeatureProcessor
    -> FeatureWriter [gtf_pro_workspace]
FeatureWriter
    DATASET = @Value(_tempDir)/export.xml
    DATASET_ATTR = _dataset
    FEATURE_TYPE_LIST_ATTR = _feature_type
    FORMAT = GML
    GML_COORDINATE_SYSTEM_GRANULARITY = DATASET
    GML_DESTINATION_DATASETTYPE_VALIDATION = Yes
    GML_DOCUMENTS_TO_WRITE = BOTH
    GML_INDENT_SIZE = 1
    GML_PREFER_POLYGON_OVER_SURFACE = no
    GML_PRETTY_PRINT = No
    GML_PROFILE = 3.1.1
    GML_REPLACE_TABS_WITH_SPACES = No
    GML_SUPPRESS_XSI_SCHEMALOCATION = no
    GML_SYSTEM_ENCODING = utf-8
    GML_TARGET_NS_PREFIX = gex
    GML_TARGET_NS_URI = http://www.veremes.com/gtf/export
    GML_TEXT_INDENT = No
    GML_USE_STYLESHEET_RESULT_AS_DATASET = no
    GML_VALIDATE_OUTPUT_DATASET = NO
    GML_WRITE_ALL_FEATURE_TYPE_DEFNS = no
    TOTAL_FEATURES_WRITTEN_ATTR = _total_features_written
    WRITER_DIRECTIVES = PREFER_POLYGON_OVER_SURFACE,no,WRITE_ALL_FEATURE_TYPE_DEFNS,no,TARGET_NS_PREFIX,gex,INDENT_SIZE,1,USE_STYLESHEET_RESULT_AS_DATASET,no,PRETTY_PRINT_SETTINGS,FME_DISCLOSURE_OPEN,PROFILE,3.1.1,FEATURE_COLLECTION_GROUP,FME_DISCLOSURE_CLOSED,TEXT_INDENT,No,GML_WRT_ADV_PARAMETERS,FME_DISCLOSURE_OPEN,SUPPRESS_XSI_SCHEMALOCATION,no,COORDINATE_SYSTEM_GRANULARITY,DATASET,VALIDATE_OUTPUT_DATASET,NO,TARGET_NS_URI,http://www.veremes.com/gtf/export,DESTINATION_DATASETTYPE_VALIDATION,Yes,DOCUMENTS_TO_WRITE,BOTH,SYSTEM_ENCODING,utf-8,REPLACE_TABS_WITH_SPACES,No,PRETTY_PRINT,No
    SUMMARY -> FeatureMerger [REQUESTOR]
FeatureMerger
    ATTR_ACCUM_MODE = Merge Supplier
    ATTR_CONFLICT_RES = Use Requestor
    CLEANING_TOLERANCE = None
    IGNORE_NULLS = No
    JOIN_KEYS = 1 1 AUTO
    MERGE_TYPE = Attributes Only
    PROCESS_DUPS = No
    REJECT_NULL_MISSING_KEYS = No
    SUPPLIERS_FIRST = No
    MERGED -> PythonCaller_2
PythonCaller_2
    PYTHONSOURCE:
      # -*- coding: utf-8 -*-
      import fmeobjects
      import zipfile
      import sys
      import os
      import shutil

      def zip_folder(folder_path, output_path):
          parent_folder = os.path.dirname(folder_path)
          contents = os.walk(folder_path)
          try:
              zip_file = zipfile.ZipFile(output_path, 'w', zipfile.ZIP_DEFLATED)
              for root, folders, files in contents:
                  for folder_name in folders:
                      absolute_path = os.path.join(root, folder_name)
                      relative_path = absolute_path.replace(parent_folder + '//','')
                      zip_file.write(absolute_path, relative_path)
                  for file_name in files:
                      absolute_path = os.path.join(root, file_name)
                      relative_path = absolute_path.replace(parent_folder + '//','')
                      zip_file.write(absolute_path, relative_path)
          except IOError, message:
              print message
              sys.exit(1)
          except OSError, message:
              print message
              sys.exit(1)
          except zipfile.BadZipfile, message:
              print message
              sys.exit(1)
          finally:
              zip_file.close()

      def FeatureProcessor(feature):
          if os.path.exists(feature.getAttribute('_tempDir')):
              zip_folder(feature.getAttribute('_tempDir') + '//',FME_MacroValues['destGexFile'])
    PYTHONSYMBOL = FeatureProcessor
Note: Ecriture du fichier GML
gtf_pro_workspace (writer GML_1)
    attributes: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

Bookmark: Récupère le nom de la catégorie
Note: s_gtf.category
category (reader POSTGRES_1)
    attributes: category_id int4,PRIKEY, name varchar(50), description varchar(200)
    -> AttributeRemover_2
AttributeRemover_2
    REMOVE_ATTRS = description
    -> AttributeRenamer_2
AttributeRenamer_2
    ATTR_LIST = name,category_name,""
    -> FeatureMerger_3 [SUPPLIER]
FeatureMerger_3
    IGNORE_NULLS = Yes
    JOIN_KEYS = @Value(category_id) @Value(category_id)
    MERGE_TYPE = Attributes Only
    PROCESS_DUPS = No
    SUPPLIERS_FIRST = No
    SUPPLIER_PREFIX_DUMMY = YES
    MERGED -> FeatureMerger_2 [REQUESTOR]
    NOT_MERGED -> FeatureMerger_2 [REQUESTOR]
